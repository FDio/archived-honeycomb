module vbd-impl {
    yang-version 1;
    namespace "urn:opendaylight:params:xml:ns:yang:vbd:impl";
    prefix "vbd-impl";

    import config { prefix config; revision-date 2013-04-05; }
    import opendaylight-md-sal-binding { prefix md-sal-binding; revision-date 2013-10-28;}

    description
        "Service definition for vbd project";

    revision "2016-02-02" {
        description
            "Initial revision";
    }

    identity vbd {
        base config:module-type;
        config:java-name-prefix Vbd;
    }

    augment "/config:modules/config:module/config:configuration" {
        case vbd {
            when "/config:modules/config:module/config:type = 'vbd'";
            container broker {
                uses config:service-ref {
                    refine type {
                        mandatory true;
                        config:required-identity md-sal-binding:binding-broker-osgi-registry;
                    }
                }
            }
        }
    }
}
